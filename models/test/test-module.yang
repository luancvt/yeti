module test-module {
  namespace "urn:example:test-module";
  prefix tm;

  description "A minimal YANG module for testing Yeti.";

  container logging {
    presence "Enables logging";
    description "Logging configuration; presence enables the feature.";
  }

  container interfaces {
    description "Top-level container for interfaces.";
    config true;

    list interface {
      key "name";
      description "An interface entry.";

      leaf name {
        type string;
        description "The name of the interface.";
      }

      leaf mtu {
        type uint16 {
          range "68..9192";
        }
        default "1500";
        description "The MTU of the interface.";
      }

      leaf enabled {
        type boolean;
        default "true";
        description "Whether the interface is enabled.";
      }

      leaf-list tags {
        type string;
        description "Tags associated with this interface.";
      }

      leaf speed {
        type enumeration {
          enum 10M;
          enum 100M;
          enum 1G;
          enum 10G;
        }
        description "The speed of the interface.";
      }

      leaf intf-description {
        type string {
          pattern "[A-Za-z][A-Za-z0-9 ]*";
        }
        description "A human-readable description of the interface.";
      }

      leaf admin-status {
        type enumeration {
          enum up;
          enum down;
        }
        mandatory true;
        description "Administrative status of the interface.";
      }

      leaf bandwidth {
        type uint64;
        units "bps";
        description "Configured bandwidth of the interface.";
      }

      container counters {
        config false;
        description "Interface counters (state data).";

        leaf in-octets {
          type uint64;
          description "Total bytes received.";
        }

        leaf out-octets {
          type uint64;
          description "Total bytes transmitted.";
        }

        container error-counters {
          description "Error counters nested inside counters.";

          leaf in-errors {
            type uint64;
            description "Total input errors.";
          }

          leaf out-errors {
            type uint64;
            description "Total output errors.";
          }
        }
      }
    }
  }
}
